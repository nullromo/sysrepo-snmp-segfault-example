module example-module {
    yang-version 1.1;
    namespace 'urn:example-module';
    prefix example;

    organization '';
    contact '';
    description '';
    revision 2022-04-28 {
        description '';
    }

    container example-data {
        description '';
        config false;

        leaf thing {
            type string;
        }
    }
}
